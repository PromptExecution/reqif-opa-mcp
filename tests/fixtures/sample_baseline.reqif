# Test Baseline 2026.01
Sample ReqIF baseline for end-to-end integration testing

## REQ-CYBER-001
System shall use strong cryptographic algorithms for data encryption.
- Key: CYBER-ENC-001
- Subtypes: CYBER
- Status: active
- Severity: high
- Owner: security-team
- Verify_Method: analysis

## REQ-AC-001
System shall require authentication for all protected resources.
- Key: AC-AUTH-001
- Subtypes: ACCESS_CONTROL
- Status: active
- Severity: high
- Owner: security-team
- Verify_Method: test

## REQ-DP-001
System shall encrypt all personally identifiable information at rest.
- Key: DP-PII-001
- Subtypes: DATA_PRIVACY
- Status: active
- Severity: medium
- Owner: privacy-team
- Verify_Method: inspection

## REQ-AUDIT-001
System shall log all security-relevant events with timestamps.
- Key: AUDIT-LOG-001
- Subtypes: AUDIT
- Status: active
- Severity: medium
- Owner: compliance-team
- Verify_Method: analysis

## REQ-CYBER-AC-001
System shall support multi-factor authentication for privileged accounts.
- Key: CYBER-AC-MFA-001
- Subtypes: CYBER,ACCESS_CONTROL
- Status: active
- Severity: high
- Owner: security-team
- Verify_Method: demo
