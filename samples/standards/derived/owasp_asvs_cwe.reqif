# OWASP ASVS Functional Sample
Functional sample baseline derived from OWASP ASVS 5.0.0.

## R1
Verify that the application protects against OS command injection and that operating system calls use parameterized OS queries or use contextual command line output encoding.
- Key: V1-2-5
- Subtypes: APPSEC
- Status: active
- Severity: high
- Owner: security-engineering
- Verify_Method: analysis
- Control_ID: V1.2.5
- Source_Standard: OWASP ASVS 5.0.0
- Source_URL: https://github.com/OWASP/ASVS/releases/download/latest/OWASP_Application_Security_Verification_Standard_5.0.0_en.json
- CWE: CWE-78
- Level: 1

## R2
Verify that the application protects against Server-side Request Forgery (SSRF) attacks, by validating untrusted data against an allowlist of protocols, domains, paths and ports and sanitizing potentially dangerous characters before using the data to call another service.
- Key: V1-3-6
- Subtypes: APPSEC
- Status: active
- Severity: medium
- Owner: security-engineering
- Verify_Method: analysis
- Control_ID: V1.3.6
- Source_Standard: OWASP ASVS 5.0.0
- Source_URL: https://github.com/OWASP/ASVS/releases/download/latest/OWASP_Application_Security_Verification_Standard_5.0.0_en.json
- CWE: CWE-918
- Level: 2

## R3
Verify that when logging sensitive data, the application enforces logging based on the data's protection level. For example, it may not be allowed to log certain data, such as credentials or payment details. Other data, such as session tokens, may only be logged by being hashed or masked, either in full or partially.
- Key: V16-2-5
- Subtypes: APPSEC
- Status: active
- Severity: medium
- Owner: security-engineering
- Verify_Method: analysis
- Control_ID: V16.2.5
- Source_Standard: OWASP ASVS 5.0.0
- Source_URL: https://github.com/OWASP/ASVS/releases/download/latest/OWASP_Application_Security_Verification_Standard_5.0.0_en.json
- CWE: CWE-532
- Level: 2

## R4
Verify that input is validated to enforce business or functional expectations for that input. This should either use positive validation against an allow list of values, patterns, and ranges, or be based on comparing the input to an expected structure and logical limits according to predefined rules. For L1, this can focus on input which is used to make specific business or security decisions. For L2 and up, this should apply to all input.
- Key: V2-2-1
- Subtypes: APPSEC
- Status: active
- Severity: high
- Owner: security-engineering
- Verify_Method: analysis
- Control_ID: V2.2.1
- Source_Standard: OWASP ASVS 5.0.0
- Source_URL: https://github.com/OWASP/ASVS/releases/download/latest/OWASP_Application_Security_Verification_Standard_5.0.0_en.json
- CWE: CWE-20
- Level: 1

## R5
Verify that the application will only accept files of a size which it can process without causing a loss of performance or a denial of service attack.
- Key: V5-2-1
- Subtypes: APPSEC
- Status: active
- Severity: high
- Owner: security-engineering
- Verify_Method: analysis
- Control_ID: V5.2.1
- Source_Standard: OWASP ASVS 5.0.0
- Source_URL: https://github.com/OWASP/ASVS/releases/download/latest/OWASP_Application_Security_Verification_Standard_5.0.0_en.json
- CWE: CWE-400
- Level: 1

## R6
Verify that when the application creates file paths for file operations, instead of user-submitted filenames, it uses internally generated or trusted data, or if user-submitted filenames or file metadata must be used, strict validation and sanitization must be applied. This is to protect against path traversal, local or remote file inclusion (LFI, RFI), and server-side request forgery (SSRF) attacks.
- Key: V5-3-2
- Subtypes: APPSEC
- Status: active
- Severity: high
- Owner: security-engineering
- Verify_Method: analysis
- Control_ID: V5.3.2
- Source_Standard: OWASP ASVS 5.0.0
- Source_URL: https://github.com/OWASP/ASVS/releases/download/latest/OWASP_Application_Security_Verification_Standard_5.0.0_en.json
- CWE: CWE-22
- Level: 1

## R7
Verify that the application enforces authorization rules at a trusted service layer and doesn't rely on controls that an untrusted consumer could manipulate, such as client-side JavaScript.
- Key: V8-3-1
- Subtypes: APPSEC
- Status: active
- Severity: high
- Owner: security-engineering
- Verify_Method: analysis
- Control_ID: V8.3.1
- Source_Standard: OWASP ASVS 5.0.0
- Source_URL: https://github.com/OWASP/ASVS/releases/download/latest/OWASP_Application_Security_Verification_Standard_5.0.0_en.json
- CWE: CWE-862
- Level: 1
