# NIST SSDF Dogfood Sample
Functional sample baseline derived from NIST SSDF 1.1 (SP 800-218).

## R1
Specify which tools or tool types must or should be included in each toolchain to mitigate identified risks, as well as how the toolchain components are to be integrated with each other.
- Key: PO-3-1
- Subtypes: SECURE_SDLC
- Status: active
- Severity: medium
- Owner: security-engineering
- Verify_Method: analysis
- Control_ID: PO.3.1
- Source_Standard: NIST SSDF 1.1 (SP 800-218)
- Source_URL: https://doi.org/10.6028/NIST.SP.800-218

## R2
Perform the code review and/or code analysis based on the organization's secure coding standards, and record and triage all discovered issues and recommended remediations in the development team's workflow or issue tracking system.
- Key: PW-7-2
- Subtypes: SECURE_SDLC
- Status: active
- Severity: high
- Owner: security-engineering
- Verify_Method: analysis
- Control_ID: PW.7.2
- Source_Standard: NIST SSDF 1.1 (SP 800-218)
- Source_URL: https://doi.org/10.6028/NIST.SP.800-218

## R3
Review, analyze, and/or test the software's code to identify or confirm the presence of previously undetected vulnerabilities.
- Key: RV-1-2
- Subtypes: SECURE_SDLC
- Status: active
- Severity: high
- Owner: security-engineering
- Verify_Method: analysis
- Control_ID: RV.1.2
- Source_Standard: NIST SSDF 1.1 (SP 800-218)
- Source_URL: https://doi.org/10.6028/NIST.SP.800-218

## R4
Have a policy that addresses vulnerability disclosure and remediation, and implement the roles, responsibilities, and processes needed to support that policy.
- Key: RV-1-3
- Subtypes: SECURE_SDLC
- Status: active
- Severity: high
- Owner: security-engineering
- Verify_Method: analysis
- Control_ID: RV.1.3
- Source_Standard: NIST SSDF 1.1 (SP 800-218)
- Source_URL: https://doi.org/10.6028/NIST.SP.800-218
